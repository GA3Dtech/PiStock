# PiStock — PLM/inventory tool for FreeCAD-based workshops
# Copyright (C) 2026 GA3Dtech
#
# This program is free software: you can redistribute it and/or modify
# it under the terms of the GNU Affero General Public License as
# published by the Free Software Foundation, either version 3 of the
# License, or (at your option) any later version.
#
# This program is distributed in the hope that it will be useful,
# but WITHOUT ANY WARRANTY; without even the implied warranty of
# MERCHANTABILITY or FITNESS FOR A PARTICULAR PURPOSE.  See the
# GNU Affero General Public License for more details.
#
# You should have received a copy of the GNU Affero General Public License
# along with this program.  If not, see <https://www.gnu.org/licenses/>.

import os
import json
import getpass
import tempfile
import uuid
import urllib.request
import urllib.error
import FreeCAD as App
import FreeCADGui as Gui
from PySide6 import QtWidgets, QtCore

# Configuration de l'adresse de votre serveur FastAPI
import ssl

# Configuration : hote du serveur PiStock
# On parle en HTTPS (TLS). La verification du certificat est TOUJOURS
# active (voir build_ssl_context plus bas) : magasin de confiance
# systeme par defaut, et pour un serveur LAN, on fait confiance
# proprement a la CA locale PiStock via pistock_ca.pem / PISTOCK_CA.
# ----------------------------------------------------------------------
#  Adresse du serveur PiStock : lue depuis pistock_host.txt
# ----------------------------------------------------------------------
# Fichier place A COTE de cette macro (dans le repertoire des macros).
# Il contient l'IP (ou le nom d'hote) du serveur, par exemple :
#     192.168.1.50               -> https://192.168.1.50:8000
#     192.168.1.50:8000          -> https://192.168.1.50:8000
#     https://pistock.local:8000 -> utilise tel quel
# Si le fichier est absent ou vide, repli sur 127.0.0.1:8000 (local).
_DEFAULT_HOST = "127.0.0.1"
_DEFAULT_PORT = "8000"


def _macro_dir():
    """Repertoire de cette macro (ou chercher pistock_host.txt)."""
    try:
        return os.path.dirname(os.path.abspath(__file__))
    except NameError:
        try:
            return App.getUserMacroDir(True)
        except Exception:
            return os.getcwd()


def _read_api_host():
    """Construit l'URL de base du serveur a partir de pistock_host.txt."""
    host_file = os.path.join(_macro_dir(), "pistock_host.txt")
    raw = ""
    try:
        with open(host_file, "r", encoding="utf-8") as fh:
            for line in fh:
                line = line.strip()
                if line and not line.startswith("#"):
                    raw = line
                    break
    except (OSError, IOError):
        raw = ""
    if not raw:
        raw = _DEFAULT_HOST
    if raw.startswith("http://") or raw.startswith("https://"):
        return raw.rstrip("/")
    if ":" not in raw:
        raw = f"{raw}:{_DEFAULT_PORT}"
    return f"https://{raw}"

API_HOST = _read_api_host()
API_BASE = f"{API_HOST}/api/v1"
API_LIST = f"{API_BASE}/parts"            # GET  : liste des pièces
API_PROJECTS = f"{API_BASE}/projects"     # GET  : liste des projets
API_UPLOAD = f"{API_BASE}/parts/upload"   # POST : envoi d'un export

def build_ssl_context():
    """TLS context used for ALL requests to the PiStock server.

    Certificate verification is ALWAYS on (there is no insecure mode):
      - by default, the system trust store (strict verification) — all
        you need with a real certificate (e.g. Let's Encrypt) in prod;
      - to trust a LAN server using PiStock's local CA, drop that CA
        (ca-cert.pem) next to this macro as 'pistock_ca.pem', or set the
        PISTOCK_CA environment variable to its path. It is then trusted
        cleanly via load_verify_locations(); the server leaf, re-signed
        by that CA, keeps validating without redistributing this file.
    """
    context = ssl.create_default_context()
    ca_file = os.environ.get("PISTOCK_CA") or os.path.join(
        _macro_dir(), "pistock_ca.pem")
    if ca_file and os.path.isfile(ca_file):
        context.load_verify_locations(cafile=ca_file)
    return context


# TLS context used by every urlopen() below (see build_ssl_context).
SSL_CONTEXT = build_ssl_context()

# Emplacement où FreeCAD mémorise le dernier auteur saisi.
# 'App.ParamGet' stocke ça de façon persistante dans la config
# de FreeCAD : la valeur survit donc d'un export à l'autre et
# même après redémarrage de FreeCAD.
PARAM_PATH = "User parameter:BaseApp/Preferences/Mod/PiStock"


# ======================================================================
#  I18N — squelette de traduction
# ======================================================================
# Memo systeme : dict {lang_code: {msgid: msgstr}}. Convention :
# msgid en anglais. La langue active est lue depuis le profil FreeCAD
# (meme PARAM_PATH que LastAuthor, clé "Language"). Pour ajouter une
# chaine : wrapper avec tr("...") et completer 'fr' ci-dessous.
TRANSLATIONS = {
    "en": {},
    "fr": {
        # Titre dialog
        "PiStock — Export to database": "PiStock — Export vers la base",
        "Language:": "Langue :",
        # Modes
        "Create a new part": "Créer une nouvelle pièce",
        "Associate to an existing part":
            "Associer à une pièce existante",
        # Labels champs
        "    Name:": "    Nom :",
        "    Project:": "    Projet :",
        "    Part:": "    Pièce :",
        "Author:": "Auteur :",
        "All projects": "Tous les projets",
        "(No project)": "(Sans projet)",
        "{name} (locked)": "{name} (verrouillée)",
        "(no part)": "(aucune pièce)",
        # Validations
        "Missing field": "Champ manquant",
        "Please enter the author name.":
            "Veuillez indiquer le nom de l'auteur.",
        "Please enter a name for the new part.":
            "Veuillez indiquer le nom de la nouvelle pièce.",
        "No part": "Aucune pièce",
        "No selectable part with this filter.":
            "Aucune pièce sélectionnable avec ce filtre.",
        "Locked part": "Pièce verrouillée",
        "Part '{name}' is locked. Unlock it from the web interface before pushing a new revision.":
            "La pièce '{name}' est verrouillée. Déverrouillez-la depuis l'interface web avant de pousser une nouvelle révision.",
        # Notification changement de langue
        "Language preference saved. The new language will be active at the next launch of this macro.":
            "Préférence de langue enregistrée. La nouvelle langue sera active au prochain lancement de cette macro.",
    },
}


def get_lang() -> str:
    """Lit la preference langue depuis le profil FreeCAD."""
    try:
        params = App.ParamGet(PARAM_PATH)
        lang = params.GetString("Language", "en")
        return lang if lang in TRANSLATIONS else "en"
    except Exception:
        return "en"


def set_lang(lang: str) -> None:
    """Persiste la preference langue dans le profil FreeCAD."""
    if lang not in TRANSLATIONS:
        return
    try:
        params = App.ParamGet(PARAM_PATH)
        params.SetString("Language", lang)
    except Exception:
        pass


def tr(text: str) -> str:
    """Traduit selon la langue active. Si pas de traduction, renvoie
    la chaine source."""
    return TRANSLATIONS.get(get_lang(), {}).get(text, text)


# ----------------------------------------------------------------------
#  MÉMORISATION DE L'AUTEUR (préférences FreeCAD)
# ----------------------------------------------------------------------
def get_remembered_author():
    """Renvoie le dernier auteur saisi. Au tout premier lancement
    (aucune valeur mémorisée), retombe sur le nom système."""
    params = App.ParamGet(PARAM_PATH)
    # 2e argument = valeur par défaut si la clé n'existe pas encore
    return params.GetString("LastAuthor", getpass.getuser())


def remember_author(author):
    """Mémorise l'auteur pour qu'il soit pré-rempli au prochain export."""
    params = App.ParamGet(PARAM_PATH)
    params.SetString("LastAuthor", author)


# ----------------------------------------------------------------------
#  COMMUNICATION AVEC L'API
# ----------------------------------------------------------------------
def fetch_existing_parts():
    """Récupère la liste des pièces déjà présentes dans la base.
    Format enrichi : id, part_name, id_project, project_code, locked.
    Retourne [] si l'API est injoignable."""
    try:
        with urllib.request.urlopen(API_LIST, timeout=5, context=SSL_CONTEXT) as response:
            data = response.read().decode("utf-8")
            return json.loads(data)
    except Exception as e:
        App.Console.PrintWarning(
            f"⚠️  Impossible de récupérer la liste des pièces : {e}\n"
        )
        return []


def fetch_existing_projects():
    """Récupère la liste des projets pour permettre le filtrage.
    Format : [{id, code, description}, ...]. [] si echec."""
    try:
        with urllib.request.urlopen(API_PROJECTS, timeout=5, context=SSL_CONTEXT) as response:
            data = response.read().decode("utf-8")
            return json.loads(data)
    except Exception as e:
        App.Console.PrintWarning(
            f"⚠️  Impossible de récupérer les projets : {e}\n"
        )
        return []


# ----------------------------------------------------------------------
#  BOITE DE DIALOGUE PySide6
# ----------------------------------------------------------------------
class PiStockExportDialog(QtWidgets.QDialog):
    """Fenêtre qui demande à quelle pièce associer l'export
    (existante ou nouvelle) et le nom de l'auteur.

    Pour les pièces existantes : un sélecteur de PROJET permet de
    filtrer la liste, et les pièces verrouillées apparaissent grisées
    avec un cadenas 🔒 — non sélectionnables."""

    # Cle interne du combobox projet : '' = tous, '__none__' = sans projet
    PROJECT_ALL = ""
    PROJECT_NONE = "__none__"

    def __init__(self, default_part_name, existing_parts,
                 existing_projects, parent=None):
        super().__init__(parent)
        self.setWindowTitle(tr("PiStock — Export to database"))
        self.setMinimumWidth(440)

        self.existing_parts = existing_parts        # [{id, part_name, id_project, project_code, locked}, ...]
        self.existing_projects = existing_projects  # [{id, code, description}, ...]
        # Résultat rempli à la validation :
        self.result_part_id = None     # int   -> pièce existante
        self.result_part_name = None   # str   -> nouvelle pièce
        self.result_author = None      # str

        layout = QtWidgets.QVBoxLayout(self)

        # --- Sélecteur de langue (en haut à droite) -----------------
        # Au changement, on persiste la nouvelle langue mais on
        # AFFICHE UN MESSAGE plutot que de rebuilder le dialog en
        # cours. Le rebuild complet d'un QDialog modal est complexe
        # (binding des widgets a recreer) — message + relance par
        # l'utilisateur est plus simple et fiable pour un squelette.
        lang_row = QtWidgets.QHBoxLayout()
        lang_row.addStretch()
        lang_row.addWidget(QtWidgets.QLabel(tr("Language:")))
        self.lang_combo = QtWidgets.QComboBox()
        self.lang_combo.addItem("EN", "en")
        self.lang_combo.addItem("FR", "fr")
        current = get_lang()
        for i in range(self.lang_combo.count()):
            if self.lang_combo.itemData(i) == current:
                self.lang_combo.setCurrentIndex(i)
                break
        self.lang_combo.currentIndexChanged.connect(self._on_lang_change)
        lang_row.addWidget(self.lang_combo)
        layout.addLayout(lang_row)

        # --- Choix : nouvelle pièce OU pièce existante ---------------
        self.radio_new = QtWidgets.QRadioButton(tr("Create a new part"))
        self.radio_existing = QtWidgets.QRadioButton(
            tr("Associate to an existing part")
        )
        layout.addWidget(self.radio_new)

        # Champ nom de la nouvelle pièce (pré-rempli avec le doc FreeCAD)
        self.new_name_edit = QtWidgets.QLineEdit(default_part_name)
        new_name_row = QtWidgets.QHBoxLayout()
        new_name_row.addWidget(QtWidgets.QLabel(tr("    Name:")))
        new_name_row.addWidget(self.new_name_edit)
        layout.addLayout(new_name_row)

        layout.addWidget(self.radio_existing)

        # --- Filtre projet (nouveau) ---------------------------------
        # Permet de réduire la liste des pièces affichées en dessous.
        self.project_combo = QtWidgets.QComboBox()
        self.project_combo.addItem(tr("All projects"), self.PROJECT_ALL)
        self.project_combo.addItem(tr("(No project)"), self.PROJECT_NONE)
        for proj in existing_projects:
            desc = proj.get("description") or ""
            label = f"{proj['code']}"
            if desc:
                # Tronque les descriptions trop longues dans le combo
                short = desc[:40] + ("…" if len(desc) > 40 else "")
                label = f"{proj['code']} — {short}"
            # On stocke le CODE projet comme userData pour filtrer
            self.project_combo.addItem(label, proj["code"])
        project_row = QtWidgets.QHBoxLayout()
        project_row.addWidget(QtWidgets.QLabel(tr("    Project:")))
        project_row.addWidget(self.project_combo)
        layout.addLayout(project_row)

        # --- Menu déroulant des pièces existantes --------------------
        # Rempli/filtré par _refresh_parts_combo() selon le projet choisi.
        self.existing_combo = QtWidgets.QComboBox()
        existing_row = QtWidgets.QHBoxLayout()
        existing_row.addWidget(QtWidgets.QLabel(tr("    Part:")))
        existing_row.addWidget(self.existing_combo)
        layout.addLayout(existing_row)

        # Filtrage au changement de projet
        self.project_combo.currentIndexChanged.connect(
            self._refresh_parts_combo)

        # --- Champ auteur --------------------------------------------
        layout.addSpacing(8)
        author_row = QtWidgets.QHBoxLayout()
        author_row.addWidget(QtWidgets.QLabel(tr("Author:")))
        self.author_edit = QtWidgets.QLineEdit(get_remembered_author())
        author_row.addWidget(self.author_edit)
        layout.addLayout(author_row)

        # --- Boutons OK / Annuler ------------------------------------
        buttons = QtWidgets.QDialogButtonBox(
            QtWidgets.QDialogButtonBox.Ok
            | QtWidgets.QDialogButtonBox.Cancel
        )
        buttons.accepted.connect(self.on_accept)
        buttons.rejected.connect(self.reject)
        layout.addWidget(buttons)

        # --- État initial --------------------------------------------
        has_existing = len(existing_parts) > 0
        self.radio_existing.setEnabled(has_existing)
        self.radio_new.setChecked(True)
        if not has_existing:
            self.existing_combo.setEnabled(False)
            self.project_combo.setEnabled(False)

        self.radio_new.toggled.connect(self._update_fields)
        self._refresh_parts_combo()  # remplit la liste initiale
        self._update_fields()

    def _refresh_parts_combo(self):
        """Remplit le combo des pièces selon le filtre projet actuel.
        Les pièces verrouillées sont prefixées 🔒 et désactivées."""
        filter_code = self.project_combo.currentData()
        self.existing_combo.clear()

        for part in self.existing_parts:
            # Filtrage par projet
            if filter_code == self.PROJECT_ALL:
                pass  # tout passe
            elif filter_code == self.PROJECT_NONE:
                if part.get("id_project") is not None:
                    continue
            else:
                if part.get("project_code") != filter_code:
                    continue

            locked = part.get("locked", False)
            # Label avec prefixe verrou si verrouillee
            label = (f"🔒 " + tr("{name} (locked)").format(name=part['part_name'])
                     if locked else part["part_name"])
            self.existing_combo.addItem(label, part["id"])

            # Desactiver l'item si la piece est verrouillee.
            # En PySide6 on accede a l'item via le modele du combobox.
            if locked:
                idx = self.existing_combo.count() - 1
                item = self.existing_combo.model().item(idx)
                if item is not None:
                    item.setEnabled(False)

        # Si la liste resultante est vide (aucune piece pour ce filtre),
        # on l'indique a l'utilisateur via un item desactive.
        if self.existing_combo.count() == 0:
            self.existing_combo.addItem(tr("(no part)"), None)
            item = self.existing_combo.model().item(0)
            if item is not None:
                item.setEnabled(False)

    def _update_fields(self):
        """Grise les champs non pertinents selon le mode choisi."""
        is_new = self.radio_new.isChecked()
        self.new_name_edit.setEnabled(is_new)
        has_existing = len(self.existing_parts) > 0
        self.project_combo.setEnabled((not is_new) and has_existing)
        self.existing_combo.setEnabled((not is_new) and has_existing)

    def on_accept(self):
        """Validation : on vérifie les saisies avant de fermer."""
        author = self.author_edit.text().strip()
        if not author:
            QtWidgets.QMessageBox.warning(
                self, tr("Missing field"),
                tr("Please enter the author name.")
            )
            return
        self.result_author = author

        if self.radio_new.isChecked():
            name = self.new_name_edit.text().strip()
            if not name:
                QtWidgets.QMessageBox.warning(
                    self, tr("Missing field"),
                    tr("Please enter a name for the new part.")
                )
                return
            self.result_part_name = name
            self.result_part_id = None
        else:
            # Pièce existante : recupere l'id stocke dans l'item
            chosen_id = self.existing_combo.currentData()
            if chosen_id is None:
                # Aucune piece selectionnable (filtre vide)
                QtWidgets.QMessageBox.warning(
                    self, tr("No part"),
                    tr("No selectable part with this filter.")
                )
                return
            # Double-check : si l'utilisateur a reussi a selectionner
            # un item desactive (en theorie impossible), on bloque.
            chosen = next((p for p in self.existing_parts
                            if p["id"] == chosen_id), None)
            if chosen and chosen.get("locked"):
                QtWidgets.QMessageBox.warning(
                    self, tr("Locked part"),
                    tr("Part '{name}' is locked. Unlock it from the "
                       "web interface before pushing a new revision.").format(
                        name=chosen['part_name'])
                )
                return
            self.result_part_id = chosen_id
            self.result_part_name = None

        self.accept()

    def _on_lang_change(self):
        """Persiste la langue choisie. Comme le dialog est modal et
        deja construit, on n'essaie pas de tout rebuilder a chaud :
        on previent l'utilisateur que la nouvelle langue sera active
        au prochain lancement de la macro."""
        new_lang = self.lang_combo.currentData()
        if new_lang == get_lang():
            return  # pas de changement effectif
        set_lang(new_lang)
        QtWidgets.QMessageBox.information(
            self, tr("Language:"),
            tr("Language preference saved. The new language will be "
               "active at the next launch of this macro.")
        )


# ----------------------------------------------------------------------
#  EXPORT PRINCIPAL
# ----------------------------------------------------------------------
def export_and_send_to_pistock():
    # 1. Vérifier qu'un document est ouvert
    doc = App.activeDocument()
    if not doc:
        App.Console.PrintError("❌ Erreur : Aucun document ouvert dans FreeCAD.\n")
        return

    # SÉCURITÉ : le document doit avoir été enregistré au moins une fois
    if not doc.FileName:
        App.Console.PrintError("⚠️  Erreur : Veuillez enregistrer votre fichier (.FCStd) avant de lancer l'export.\n")
        return

    part_name = doc.Name
    App.Console.PrintMessage(f"🚀 Initialisation de l'export PiStock pour : {part_name}\n")

    # 2. Récupération des listes (pièces et projets) pour le GUI
    existing_parts = fetch_existing_parts()
    existing_projects = fetch_existing_projects()

    # 3. Affichage de la boîte de dialogue PySide6
    dialog = PiStockExportDialog(part_name, existing_parts,
                                 existing_projects,
                                 Gui.getMainWindow())
    if dialog.exec() != QtWidgets.QDialog.Accepted:
        App.Console.PrintMessage("ℹ️  Export annulé par l'utilisateur.\n")
        return

    chosen_part_id = dialog.result_part_id      # ou None
    chosen_part_name = dialog.result_part_name  # ou None
    author = dialog.result_author

    # Mémorise l'auteur : il sera pré-rempli au prochain lancement.
    remember_author(author)

    if chosen_part_id is not None:
        App.Console.PrintMessage(
            f"📌 Export associé à la pièce existante (id={chosen_part_id}).\n"
        )
    else:
        App.Console.PrintMessage(
            f"📌 Création d'une nouvelle pièce : '{chosen_part_name}'.\n"
        )
    App.Console.PrintMessage(f"✍️  Auteur : {author}\n")

    # 4. Génération des fichiers temporaires
    tmp_dir = tempfile.gettempdir()
    fcstd_temp = os.path.join(tmp_dir, f"{part_name}.FCStd")
    png_temp = os.path.join(tmp_dir, f"{part_name}.png")
    glb_temp = os.path.join(tmp_dir, f"{part_name}.glb")

    try:
        # A. Sauvegarde d'une copie propre du fichier natif
        doc.saveCopy(fcstd_temp)
        App.Console.PrintMessage(f"✔️  Fichier temporaire généré dans : {fcstd_temp}\n")

        # B. Capture d'écran (Thumbnail) de la vue active
        view = Gui.activeDocument().activeView()
        if view:
            view.saveImage(png_temp, 800, 600, "Transparent")
            App.Console.PrintMessage("✔️  Vignette .png générée.\n")
        else:
            raise Exception("Impossible d'accéder à la vue 3D active.")

        # C. Export 3D .glb (glTF binaire) avec tessellation fine
        #
        # ImportGui.export() utilise la tessellation par DEFAUT de
        # chaque objet (ViewObject.Deviation, ~0.5% de la bbox), ce
        # qui efface les chanfreins millimetriques. On contourne ca
        # en modifiant TEMPORAIREMENT la deviation de chaque objet
        # juste pour l'export, puis on restaure les valeurs originales
        # (try/finally garantit la restauration meme en cas d'erreur).
        #
        # On reste sur les Part::Feature originaux (qui ont une Shape),
        # contrairement a une tentative precedente avec MeshPart qui
        # creait des Mesh::Feature -> tous rejetes par ImportGui en
        # "null shape" car ce dernier veut des Shapes.
        all_objects = [o for o in doc.Objects if hasattr(o, "Shape")]
        if not all_objects:
            raise Exception("Le document ne contient aucun objet exportable.")

        # Backup et modification per-object des params de tessellation
        # Deviation = pourcentage de la diagonale bbox (default ~0.5)
        # AngularDeflection = en degres (default ~28.5)
        tess_backups = []
        for obj in all_objects:
            vo = getattr(obj, "ViewObject", None)
            if vo is None:
                continue
            try:
                old_dev = vo.Deviation
                old_ang = vo.AngularDeflection
                tess_backups.append((vo, old_dev, old_ang))
                # 0.01% = chanfreins millimetriques bien visibles
                vo.Deviation = 0.01
                vo.AngularDeflection = 5.0
            except (AttributeError, Exception):
                # Certains ViewObject n'ont pas ces proprietes
                # (datums, plans...). On les saute silencieusement.
                pass

        import ImportGui
        try:
            ImportGui.export(all_objects, glb_temp)
        finally:
            # Restauration des valeurs originales, meme si l'export
            # a plante. Indispensable pour ne pas laisser le document
            # dans un etat modifie pour l'utilisateur.
            for vo, dev, ang in tess_backups:
                try:
                    vo.Deviation = dev
                    vo.AngularDeflection = ang
                except Exception:
                    pass

        if os.path.exists(glb_temp):
            App.Console.PrintMessage("✔️  Fichier 3D .glb généré et prêt.\n")
        else:
            raise Exception("L'exporteur glTF de FreeCAD n'a produit aucun fichier.")

        # D. Envoi des fichiers à l'API via Multipart HTTP
        App.Console.PrintMessage("📡 Connexion au serveur PiStock et transfert...\n")

        boundary = uuid.uuid4().hex
        text_parts = []

        # Champs texte : on envoie part_id OU part_name (jamais les deux),
        # plus l'auteur dans tous les cas.
        def add_text_field(name, value):
            text_parts.append(
                f"--{boundary}\r\n"
                f"Content-Disposition: form-data; name=\"{name}\"\r\n\r\n"
                f"{value}\r\n"
            )

        if chosen_part_id is not None:
            add_text_field("part_id", chosen_part_id)
        else:
            add_text_field("part_name", chosen_part_name)
        add_text_field("author", author)

        # Fonction pour packager les fichiers
        def add_file_part(field_name, file_path, content_type):
            filename = os.path.basename(file_path)
            head = (
                f"--{boundary}\r\n"
                f"Content-Disposition: form-data; name=\"{field_name}\"; "
                f"filename=\"{filename}\"\r\n"
                f"Content-Type: {content_type}\r\n\r\n"
            )
            with open(file_path, "rb") as f:
                body = f.read()
            return head.encode("utf-8") + body + b"\r\n"

        body_bytes = b"".join([p.encode("utf-8") for p in text_parts])
        body_bytes += add_file_part("cad_file", fcstd_temp, "application/octet-stream")
        body_bytes += add_file_part("thumbnail_file", png_temp, "image/png")
        body_bytes += add_file_part("glb_file", glb_temp, "model/gltf-binary")
        body_bytes += f"--{boundary}--\r\n".encode("utf-8")

        req = urllib.request.Request(API_UPLOAD, data=body_bytes)
        req.add_header("Content-Type",
                       f"multipart/form-data; boundary={boundary}")

        with urllib.request.urlopen(req, context=SSL_CONTEXT) as response:
            res_data = response.read().decode("utf-8")
            App.Console.PrintMessage(
                f"🎉 [SUCCESS] PiStock mis à jour ! Réponse du serveur : {res_data}\n"
            )

    except urllib.error.HTTPError as e:
        # On essaie de lire le détail renvoyé par l'API
        try:
            err_body = e.read().decode("utf-8")
            err_data = json.loads(err_body)
            err_detail = err_data.get("detail", err_body)
        except Exception:
            err_detail = str(e)

        # Cas particulier : pièce verrouillée (423) -> pop-up explicite
        # car cette erreur est attendue dans le flux normal d'utilisation.
        if e.code == 423:
            App.Console.PrintWarning(f"🔒 Pièce verrouillée : {err_detail}\n")
            QtWidgets.QMessageBox.warning(
                Gui.getMainWindow(),
                "PiStock — Pièce verrouillée",
                f"Impossible de pousser cette révision.\n\n{err_detail}\n\n"
                f"Déverrouillez la pièce depuis l'interface web "
                f"(http://127.0.0.1:8000/) puis réessayez."
            )
        else:
            App.Console.PrintError(
                f"❌ Échec de l'opération (HTTP {e.code}) : {err_detail}\n"
            )
    except Exception as e:
        App.Console.PrintError(f"❌ Échec de l'opération : {str(e)}\n")

    finally:
        # 5. Nettoyage des fichiers temporaires locaux
        for f in [fcstd_temp, png_temp, glb_temp]:
            if os.path.exists(f):
                try:
                    os.remove(f)
                except Exception:
                    pass


# Lancement de l'export
export_and_send_to_pistock()
